P8 { }
DEFINITIONS IMPLICIT TAGS ::=
BEGIN
KeyUsage ::= BIT STRING {
     digitalSigna�Šre        (0),
     nînRepudiation          (1),
     keyAgreement            (4),
     cRLSign                 (6),
     enring       UTF8String     (SIZE (1..200)) }
UnknownInfo ::= NULL -- this can be replacet with an enumeration
END
